/*
 * Copyright (c) 2015 Cisco Systems, Inc. and others.  All rights reserved.
 *
 * This program and the accompanying materials are made available under the
 * terms of the Eclipse Public License v1.0 which accompanies this distribution,
 * and is available at http://www.eclipse.org/legal/epl-v10.html
 */
module tsdr-syslog-collector {

    yang-version 1;
    namespace "urn:opendaylight:params:xml:ns:yang:controller:config:tsdr-syslog-collector";
    prefix "tsdr-syslog-collector";

    import config { prefix config; revision-date 2013-04-05; }
    import opendaylight-md-sal-binding { prefix mdsal; revision-date 2013-10-28; }
    contact
      "Sharon Aicler <saichler@gmail.com>";
    description
        "This module contains the base YANG definitions for
        tsdr-syslog-collector impl implementation.";

    revision "2015-10-07" {
        description
            "Initial revision.";
    }

    // This is the definition of the service implementation as a module identity.
    identity tsdr-syslog-collector {
            base config:module-type;
            config:java-name-prefix TSDRSyslog;
    }
    augment "/config:modules/config:module/config:configuration" {
                case tsdr-syslog-collector {
                    when "/config:modules/config:module/config:type = 'tsdr-syslog-collector'";
                    container binding-aware-broker {
                        uses config:service-ref {
                            refine type {
                                mandatory false;
                                config:required-identity mdsal:binding-broker-osgi-registry;
                            }
                        }
                    }
                    container rpc-registry {
                        uses config:service-ref {
                            refine type {
                                mandatory true;
                                config:required-identity mdsal:binding-rpc-registry;
                            }
                        }
                    }
                    leaf udpport {
                        type uint16;
                    }
                    leaf tcpport {
                        type uint16;
                    }
                    leaf core-threadpool-size{
                        type uint16;
                    }leaf max-threadpool-size{
                        type uint16;
                    }leaf keep-alive-time{
                        type uint16;
                    }leaf queue-size{
                        type uint16;
                    }
                }
    }
      typedef severity-id {
            type uint16 {
                range 0..7;
            }
            description "Severity from 0 to 7";
        }

        typedef facility-id {
            type uint16 {
                range 0..23;
            }
            description "Facility from 0 to 23";
        }

        grouping meta-filter {
            leaf severity {
                type severity-id;
            }
            leaf facility {
                type facility-id;
            }
            leaf sid {
                type string;
                default ".*";
                description "Messageid of syslog";
            }
            leaf host {
                type string;
                default ".*";
                description "Hostname of syslog";
            }
            leaf application {
                type string;
                default ".*";
                description "Application name of syslog";
            }
            leaf pid{
                type string;
                default ".*";
                description "Processid of syslog";
            }
            leaf content {
                type string;
                default ".*";
                description "Content Body of syslog";
            }

        }

         rpc register-filter {
            description "register a specific severity, return a listener id to listen.";
            input {
                uses meta-filter;
                leaf callback-url{
                       type string;
                       description "the callback URL of your app ";
                }
            }
            output {
                leaf listener-id {
                    type string;
                }
            }
         }

         rpc show-register-filter {
                 description "show registered filter";
                    output {
                          leaf result{
                              type string;
                          }
                          list registered-syslog-filter {

                                          key "filter-id";
                                          leaf filter-id {
                                              type string;
                                          }
                                          leaf callback-url{
                                                type string;
                                          }
                                          container registered-filter-entity {
                                              uses meta-filter;
                                          }
                          }
                    }
                }

         rpc delete-registered-filter{
                 description "delete registered filter";

                   input {
                                 leaf filter-id{
                                     type string;

                                 }
                             }

                   output {
                                 leaf result {
                                     type string;
                                 }
                             }
         }

         rpc show-threadpool-configuration{

                   output{
                              leaf queue-remaining-capacity{
                                    type uint16;
                              }
                              leaf queue-used-capacity{
                                    type uint16;
                              }
                              leaf keep-alive-time{
                                    type uint16;
                                    description "Time Unit: Second";
                              }
                              leaf current-alive-thread-number{
                                    type uint16;
                              }
                              leaf core-thread-number{
                                    type uint16;
                              }
                              leaf Max-thread-number{
                                    type uint16;
                              }


                          }
         }

         rpc config-threadpool{
                   input{
                            leaf core-thread-number{
                                    type uint16;
                             }
                            leaf max-thread-number{
                                    type uint16;
                             }
                            leaf keep-alive-time{
                                    type uint16;
                             }

                        }

                   output{

                           leaf result{
                              type string;
                           }


                   }
         }


      container syslog-dispatcher {
            list syslog-filter {
                config true;
                key "filter-id";
                leaf filter-id {
                    type string;
                }
                container filter-entity {
                    uses meta-filter;
                }
                leaf callback-url{
                     type string;
                }
                list listener {
                    key "listener-id";
                    leaf listener-id {
                        type string;
                    }
                }
            }
            list syslog-listener {
                config false;
                key "listener-id";
                leaf listener-id {
                    type string;
                }
                leaf syslog-message {
                    type string;
                }
            }
        }
}
